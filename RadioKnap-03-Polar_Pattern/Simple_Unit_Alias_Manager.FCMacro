# ================================================================================
# Simple Unit and Alias Manager for FreeCad Spreadsheet
# ================================================================================
# ABOUT
# ================================================================================
# Macro developed for FreeCAD (http://www.freecadweb.org/).
# This macro helps managing Display Unit & Aliases inside FreeCAD Spreadsheet
# workbench. It is able to:
#        - create aliases and Unit based on Collumns selected before runnin
#        - Check for valied Unit and Alias value and mark error, see youtube video
#          for more info.
#        - delete unit & aliases
#
# More information might be found on FreeCAD forums: http://forum.freecadweb.org/
#
# LICENSE
# ================================================================================
# Original work done by tarihatari
#	(https://github.com/tarihatari/FreeCAD_Macros)
# 2016 Improved by Pablo Gil Fernandez
# 	(https://www.freecadweb.org/wiki/Macro_Alias_Manager)
# 2019 Improved by Svenn-Erik K. Thomsen
# Copyright (c) 2019 tarihatari & Pablo Gil Fernandez & Svenn-Erik K. Thomsen
#
# This work is licensed under GNU Lesser General Public License (LGPL).
# To view a copy of this license, visit https://www.gnu.org/licenses/lgpl-3.0.html.
#
# ================================================================================

__Name__          = 'Simple Unit & Alias Manager'
__Comment__       = 'Macro to set and Clear Unit and Alias in FreeCad Spreadsheet, if the Cell Properties Style in the Alias Columns is set to somthing Alias will not bee added to corresponding Value Cell'
__Author__        = 'Svenn-Erik Krengelund Thomsen'
__Version__       = '01.02.03'
__Date__          = '2019-05-03'
__License__       = 'GNU Lesser General Public License v3.0 or later'
__Web__           = 'https://www.youtube.com/channel/UCYTILmAt4gn9v8h7s6ZM49g'
__Wiki__          = 'https://github.com/sekt1953'
__Icon__          = ''
__Help__          = ''
__Status__        = 'Stable'
__Requires__      = 'FreeCAD >= v0.17'
__Communication__ = ''
__Files__         = ''


from PySide import QtGui, QtCore
from FreeCAD import Gui
from PySide.QtGui import *
from PySide.QtCore import *

import os
import string
App = FreeCAD
Gui = FreeCADGui
AppSheet = App.ActiveDocument.Spreadsheet

# ===== Global variables =================================
alphabet_ulist = list(string.ascii_uppercase)
alphabet_llist = list(string.ascii_lowercase)
alphabet_alist = alphabet_ulist + alphabet_llist

actions_list = ["Select some Action !!","Set Unit and Aliases","Clear Unit & Aliases","Exit Program","Clear Console & Report"]
validunit_list = ['','mm','m','cm','dm','km''in','\'','ft',"'",'th','kg','g','mg','t','lb','oz','st','cwt','deg','rad','gon','s','min','h','A','K','cd','mol','l'] # https://www.freecadweb.org/wiki/Units
minRow = 3
maxRow = 19
myIcon = str(os.path.dirname(os.path.abspath(__file__)) + '/Alias.png')


class myUnitError():
	def clearUnitError(self,cu):
		AppSheet.setStyle(cu, '')
		AppSheet.setForeground(cu, (0.000000,0.000000,0.000000,1.000000))
		AppSheet.setBackground(cu, (1.000000,1.000000,1.000000,1.000000))

	def setUnitError(self,cu):
		AppSheet.setStyle(cu, 'bold|italic|underline')
		AppSheet.setForeground(cu, (1.000000,1.000000,0.000000,1.000000))
		AppSheet.setBackground(cu, (1.000000,0.000000,0.000000,1.000000))
myc = myUnitError()

class p():
	def aliasManager(self):
		try:
# ===== Variables ==============================================
			mode = self.QCBAction.currentText()
			columnAlias = self.QCBAlias.currentText()
			columnUnit  = self.lCUnit.text()
			columnValue = self.lCValue.text()
			rowFrom     = self.QSBFrom.value()
			rowTo       = self.QSBTo.value()

# ===== Mode - Set Unit & Alias ================================
			if mode == actions_list[1]:
				self.QCBAction.setCurrentIndex(0)
				for i in range(rowFrom,rowTo+1):
					cellAlias = columnAlias + str(i)
					cellUnit  = columnUnit + str(i)
					cellValue = columnValue + str(i)
					cellStyle = str(AppSheet.getStyle(cellAlias))

					# set Aligment
					AppSheet.setAlignment(cellUnit, 'center|vcenter|vimplied')

					# set Alias
					if cellStyle.find('None') != -1:
						AppSheet.setAlias(cellValue, AppSheet.getContents(cellAlias))
					else:
						AppSheet.setAlias(cellValue, "")
					App.ActiveDocument.recompute()

					# set DisplayUnit
					cellValueTxt = ""
					if AppSheet.getContents(cellUnit) in validunit_list:
						AppSheet.setDisplayUnit(cellValue, AppSheet.getContents(cellUnit))
						myc.clearUnitError(cellUnit)
					else:
						AppSheet.setDisplayUnit(cellValue, "")
						myc.setUnitError(cellUnit)
					App.ActiveDocument.recompute()

# ===== Mode - Clear Unit & Alias ==============================
			elif mode == actions_list[2]:
				self.QCBAction.setCurrentIndex(0)
				for i in range(rowFrom,rowTo+1):
					cellAlias = columnAlias + str(i)
					cellUnit  = columnUnit + str(i)
					cellValue = columnValue + str(i)

					# set Aligment
					AppSheet.setAlignment(cellUnit, 'center|vcenter|vimplied')

					# clear Alias
					AppSheet.setAlias(cellValue, "")
					App.ActiveDocument.recompute()

					# clear DisplayUnit
					AppSheet.setDisplayUnit(cellValue, "")
					if AppSheet.getContents(cellUnit) in validunit_list:
						myc.clearUnitError(cellUnit)
					else:
						myc.setUnitError(cellUnit)
					App.ActiveDocument.recompute()

# ===== Mode - Exit Program ====================================
			elif mode == actions_list[3]:
				self.QCBAction.setCurrentIndex(0)
				self.close()

# ===== Clear Console & Report View ============================
			elif mode == actions_list[4]:
				self.QCBAction.setCurrentIndex(0)
				#from PySide import QtGui
				mw=Gui.getMainWindow()
				c=mw.findChild(QtGui.QPlainTextEdit, "Python console")
				c.clear()
				r=mw.findChild(QtGui.QTextEdit, "Report view")
				r.clear()


# ===== If errors ==============================================
			#else:
			#	FreeCAD.Console.PrintMessage("\n "+mode+"\n" + str(validunit_list[28]))
				#xx = list(AppSheet.getStyle('A3'))
				#if xx.find('italic') != -1:
				#FreeCAD.Console.PrintMessage("\nThis is in Italic")
				#FreeCAD.Console.PrintMessage("\nStyle: " + str(xx))
				#FreeCAD.Console.PrintMessage("\nBackground: " + str(AppSheet.getBackground('C3')))
				#FreeCAD.Console.PrintMessage("\nBackground: " + str(AppSheet.getBackground('C4')))

		except:
			FreeCAD.Console.PrintError("\nUnable to complete task\n")
			#self.close()

	def onRowFromChange(self):
		#FreeCAD.Console.PrintMessage("\nonRowFromChange: "+ str(self.QSBFrom.value()))
		self.QSBTo.setMinimum(self.QSBFrom.value())

	def onRowToChange(self):
		#FreeCAD.Console.PrintMessage("\nonRowToChange: "+ str(self.QSBTo.value()))
		self.QSBFrom.setMaximum(self.QSBTo.value())

	def onActionChange(self):
		#FreeCAD.Console.PrintMessage("\nonActionChange: "+self.QCBAction.currentText()+" "+ str(self.QCBAction.currentIndex()))
		self.aliasManager()

	def onAliasChange(self):
		#FreeCAD.Console.PrintMessage("\nonAliasChange: "+self.QCBAlias.currentText()+" "+ str(self.QCBAlias.currentIndex()))
		self.lCUnit.setText(alphabet_ulist[self.QCBAlias.currentIndex()+1])
		self.lCValue.setText(alphabet_ulist[self.QCBAlias.currentIndex()+2])

	def close(self):
		self.dialog.hide()
# ========================================================
# ===== GUI menu ========================================
# ========================================================
	def __init__(self):
		self.dialog = None
		self.dialog = QtGui.QDialog()
		self.dialog.resize(350,150)
		self.dialog.setWindowTitle(__Name__ + " Ver.: " + __Version__)

		# Grid setup
		# SpreadsheetFile
		lFSheet = QtGui.QLabel("Spreadsheet:")
		lFSheet.setAlignment(QtCore.Qt.AlignLeft | QtCore.Qt.AlignVCenter)

		lFFile = QtGui.QLabel("Select Spreadsheet:")
		lFFile.setAlignment(QtCore.Qt.AlignRight | QtCore.Qt.AlignVCenter)
		self.QCBFile = QtGui.QComboBox()
		self.image_01 = myIcon #"/home/sekt/.FreeCAD/Macro/Alias.png"
		icon01 = QtGui.QIcon()
		icon01.addPixmap(QtGui.QPixmap(self.image_01),QtGui.QIcon.Normal, QtGui.QIcon.Off)
		self.QCBFile.addItem(icon01, "myIcon")

		# Columns
		lCColums = QtGui.QLabel("Columns:")
		lCColums.setAlignment(QtCore.Qt.AlignLeft | QtCore.Qt.AlignVCenter)

		lCAlias = QtGui.QLabel("Alias:")
		lCAlias.setAlignment(QtCore.Qt.AlignRight | QtCore.Qt.AlignVCenter)
		self.QCBAlias = QtGui.QComboBox()
		for i in alphabet_ulist:
			self.QCBAlias.addItem(i)
		self.QCBAlias.setCurrentIndex(0) # set default item 'A'
		self.QCBAlias.currentIndexChanged.connect(self.onAliasChange)

		lCUnit = QtGui.QLabel("Display unit:")
		lCUnit.setAlignment(QtCore.Qt.AlignRight | QtCore.Qt.AlignVCenter)
		self.lCUnit = QtGui.QLabel(alphabet_ulist[self.QCBAlias.currentIndex()+1])
		self.lCUnit.setAlignment(QtCore.Qt.AlignLeft | QtCore.Qt.AlignVCenter)

		lCValue = QtGui.QLabel("Column to format:")
		lCValue.setAlignment(QtCore.Qt.AlignRight | QtCore.Qt.AlignVCenter)
		self.lCValue = QtGui.QLabel(alphabet_ulist[self.QCBAlias.currentIndex()+2])
		self.lCValue.setAlignment(QtCore.Qt.AlignLeft | QtCore.Qt.AlignVCenter)

		# Rows
		lR0 = QtGui.QLabel("Rows:")
		lR0.setAlignment(QtCore.Qt.AlignLeft | QtCore.Qt.AlignVCenter)

		lR1 = QtGui.QLabel("From Row:")
		lR1.setAlignment(QtCore.Qt.AlignRight | QtCore.Qt.AlignVCenter)
		self.QSBFrom = QtGui.QSpinBox()
		self.QSBFrom.setValue(minRow) # set default item
		self.QSBFrom.setSingleStep(1)
		#self.QSBFrom.setMinimum(minRow)
		#self.QSBFrom.setMaximum(maxRow)
		self.QSBFrom.valueChanged.connect(self.onRowFromChange)

		lR2 = QtGui.QLabel("To Row:")
		lR2.setAlignment(QtCore.Qt.AlignRight | QtCore.Qt.AlignVCenter)
		self.QSBTo = QtGui.QSpinBox()
		self.QSBTo.setValue(maxRow) # set default item
		self.QSBTo.setSingleStep(1)
		#self.QSBTo.setMinimum(minRow)
		#self.QSBTo.setMaximum(maxRow)
		self.QSBTo.valueChanged.connect(self.onRowToChange)

		# Action
		self.QPBAbout = QtGui.QPushButton('About')

		lA0 = QtGui.QLabel("Action:")
		lA0.setAlignment(QtCore.Qt.AlignLeft | QtCore.Qt.AlignVCenter)
		self.QCBAction = QtGui.QComboBox()
		self.QCBAction.addItems(actions_list)
		self.QCBAction.insertSeparator(1)
		self.QCBAction.insertSeparator(4)
		self.QCBAction.setCurrentIndex(0) # set default item
		self.QCBAction.currentIndexChanged.connect(self.onActionChange)

		grid = QtGui.QGridLayout()
		grid.setSpacing(10)

		# Files
		grid.addWidget(lFSheet,         1, 0, 1, 1)
		grid.addWidget(lFFile,          2, 1, 1, 1)
		grid.addWidget(self.QCBFile,    2, 2, 1, 1)
		# Columns:
		grid.addWidget(lCColums,        3, 0, 1, 1)
		grid.addWidget(lCAlias,         4, 1, 1, 1)
		grid.addWidget(self.QCBAlias,   4, 2, 1, 1)
		grid.addWidget(lCUnit,          5, 1, 1, 1)
		grid.addWidget(self.lCUnit,     5, 2, 1, 1)
		grid.addWidget(lCValue,         6, 1, 1, 1)
		grid.addWidget(self.lCValue,    6, 2, 1, 1)
		# Rows
		grid.addWidget(lR0,             7, 0, 1, 1)
		grid.addWidget(lR1,             8, 1, 1, 1)
		grid.addWidget(self.QSBFrom,    8, 2, 1, 1)
		grid.addWidget(lR2,             9, 1, 1, 1)
		grid.addWidget(self.QSBTo,      9, 2, 1, 1)
		# Action
		grid.addWidget(lA0,            10, 0, 1, 1)
		grid.addWidget(self.QPBAbout,  11, 0, 1, 1)
		grid.addWidget(self.QCBAction, 11, 1, 1, 2)

		self.dialog.setLayout(grid)
		self.QCBAlias.setFocus()

		self.dialog.show()
		self.dialog.exec_()

p()
